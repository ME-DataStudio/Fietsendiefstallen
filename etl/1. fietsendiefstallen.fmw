FME workspace 1. fietsendiefstallen.fmw

Parameters:
- SourceDataset_XLSXR = $(FME_MF_DIR)Diefstal fiets Groningen stad vanaf 2013.xlsx   # Source Microsoft Excel File(s)
- DestDataset_ESRISHAPE = $(FME_MF_DIR)fietsendiefstal.shp   # Destination Esri Shapefile Folder

Readers:
- XLSXR_1: XLSXR from $(SourceDataset_XLSXR)

Writers:
- ESRISHAPE_1: ESRISHAPE to $(DestDataset_ESRISHAPE) in EPSG:4326

Note: Auteur: Anwar Ibrahim / Datum: 1-10-2017 / Versie: 0.1 / Omschrijving: / XY RD coordinaten van fietsendiefstallen omzetten naar lat/lon en wegschrijven naar een shape.
Incidenten (reader XLSXR_1)
    attributes: Incident Identificatie char(19), Bronregistratie char(22), Incidentsoort code char(4), Incidentsoort char(15), Pleegstraatnaam char(34), Pleeghuisnummer met toev. char(8), Pleegpostcode char(7), Pleegplaats char(10), Pleeggemeente char(10), Pleegprovincie char(10), Pleegwijk char(36), Pleegbuurt char(23), Pleegsubbuurt char(23), Begin-pleegdag v/d week char(10), Begin-pleegdagdeel char(8), Begin-pleegdatum/tijd datetime, Eind-pleegdag v/d week char(10), Eind-pleegdagdeel char(8), Eind-pleegdatum/tijd datetime, Kennisnamedag v/d week char(10), Kennisnamedagdeel char(8), Kennisnamedatum/tijd datetime, Aangifte char(2), Poging char(2), Verdachten number(2,0), Aanhoudingen number(2,0), Opgehelderd char(2), Object char(41), Project(en) char(47), Temperatuur char(5),
      Weer char(33), X char(7), Y number(7,0)
    -> VertexCreator
VertexCreator
    MODE_NAME = Add Point
    YVAL = @Value(Y)
    XVAL = @Value(X)
    -> CoordinateSystemSetter
CoordinateSystemSetter
    COORDSYS = EPSG:28992
    -> HullAccumulator
    -> AttributeManager
AttributeManager
    ATTR_TABLE:
      RENAME_SET_VALUE Incident Identificatie > Identificatie
      RENAME_SET_VALUE Bronregistratie > Bronr
      RENAME_SET_VALUE Incidentsoort code > soort code
      RENAME_SET_VALUE Pleegstraatnaam > straatnaam
      RENAME_SET_VALUE Pleeghuisnummer met toev. > hsnrtoev
      RENAME_SET_VALUE Pleegpostcode > postcode
      RENAME_SET_VALUE Pleegplaats > plaats
      RENAME_SET_VALUE Pleeggemeente > gemeente
      RENAME_SET_VALUE Pleegprovincie > provincie
      RENAME_SET_VALUE Pleegwijk > wijk
      RENAME_SET_VALUE Pleegbuurt > buurt
      RENAME_SET_VALUE Pleegsubbuurt > subbuurt
      RENAME_SET_VALUE Begin-pleegdag v/d week > Begin-dag
      RENAME_SET_VALUE Begin-pleegdagdeel > Begin-dagdeel
      RENAME_SET_VALUE Begin-pleegdatum/tijd > Begin-datum/tijd
      RENAME_SET_VALUE Eind-pleegdag v/d week > Eind-dag
      RENAME_SET_VALUE Eind-pleegdagdeel > Eind-dagdeel
      RENAME_SET_VALUE Eind-pleegdatum/tijd > Eind-datum/tijd
      RENAME_SET_VALUE Kennisnamedag v/d week > Kndag
      RENAME_SET_VALUE Kennisnamedagdeel > Kndagdeel
      RENAME_SET_VALUE Kennisnamedatum/tijd > Kndatum/tijd
    -> Reprojector
Reprojector
    SOURCE = EPSG:28992
    INTERPOLATION_TYPE_NAME = Nearest Neighbor
    RASTER_CELL_SIZE = Preserve Cells
    DEST = EPSG:4326
    REPROJECTED -> CoordinateExtractor
CoordinateExtractor
    X_ATTR = lon
    Y_ATTR = lat
    IND = 0
    MODE = Specify Coordinate
    -> Incidenten (writer ESRISHAPE_1)
Incidenten (writer ESRISHAPE_1)
    attributes: Identifica char(200), Bronr char(200), soort_code char(200), Incidentso char(15), straatnaam char(200), hsnrtoev char(200), postcode char(200), plaats char(200), gemeente char(200), provincie char(200), wijk char(200), buurt char(200), subbuurt char(200), Begin_dag char(200), Begin_dagd char(200), Begin_datu char(200), Eind_dag char(200), Eind_dagde char(200), Eind_datum char(200), Kndag char(200), Kndagdeel char(200), Kndatum_ti char(200), Aangifte char(2), Poging char(2), Verdachten number(2,0), Aanhouding number(2,0), Opgehelder char(2), Object char(41), Project(en char(47), Temperatuu char(5),
      Weer char(33), X char(7), Y number(7,0), lon char(200), lat char(200)
Note: Maak een boundary
HullAccumulator
    HULLTYPE_PARAM = Concave )(
    3DMODE_PARAM = 2D
    HULL -> Bufferer
    HULL -> Reprojector_2
Reprojector_2
    SOURCE = EPSG:28992
    INTERPOLATION_TYPE_NAME = Nearest Neighbor
    RASTER_CELL_SIZE = Preserve Cells
    DEST = EPSG:4326
    REPROJECTED -> boundary (writer ESRISHAPE_1)
boundary (writer ESRISHAPE_1)
Note: Buffer van +500m voor de BAG
Bufferer
    CAP_STYLE = Round
    ANGLE = 22.5
    OFFSET = 500
    CORNER_STYLE = Round
    BUFFERED -> Reprojector_3
Reprojector_3
    SOURCE = EPSG:28992
    INTERPOLATION_TYPE_NAME = Nearest Neighbor
    RASTER_CELL_SIZE = Preserve Cells
    DEST = EPSG:4326
    REPROJECTED -> boundary_500m (writer ESRISHAPE_1)
boundary_500m (writer ESRISHAPE_1)
