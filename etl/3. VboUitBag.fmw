FME workspace 3. VboUitBag.fmw

Parameters:
- SourceDataset_ESRISHAPE = Z:\1. Anwar\AIConsultancy\Datascience Noord NL\DataUit\BAG-LL-WGS84.shp\Verblijfsobject.shp   # Source Esri Shapefile(s)
- DestDataset_ESRISHAPE = Z:\1. Anwar\AIConsultancy\Datascience Noord NL\DataUit\BAG-WGS84.shp   # Destination Esri Shapefile Folder

Readers:
- ESRISHAPE_1: ESRISHAPE from $(SourceDataset_ESRISHAPE) in EPSG:4326

Writers:
- ESRISHAPE_2: ESRISHAPE to $(DestDataset_ESRISHAPE) in EPSG:4326

Note: Auteur: Anwar Ibrahim / Datum: 1-10-2017 / Versie: 0.1 / Omschrijving: / Vergeten lat/lon coord weg te schijven
Verblijfsobject (reader ESRISHAPE_1)
    attributes: identifica char(200), opp char(200), status char(200), gebr_doel char(200), openbare_r char(200), huisnummer char(200), huisletter char(200), toevoeging char(200), postcode char(200), woonplaats char(200), bouwjaar char(200), pandidenti char(200), pandstatus char(200)
    -> CoordinateExtractor
CoordinateExtractor
    IND = 0
    MODE = Specify Coordinate
    Y_ATTR = lat
    X_ATTR = lon
    -> Verblijfsobject
    -> Verblijfsobject (writer ESRISHAPE_2)
Verblijfsobject (writer ESRISHAPE_2)
    attributes: identifica char(24), opp char(12), status char(60), gebr_doel char(60), openbare_r char(120), huisnummer char(10), huisletter char(10), toevoeging char(10), postcode char(10), woonplaats char(60), bouwjaar char(6), pandidenti char(24), pandstatus char(60), lon char(20), lat char(20)
Verblijfsobject: Inspector
