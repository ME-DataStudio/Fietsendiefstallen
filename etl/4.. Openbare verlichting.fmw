FME workspace 4.. Openbare verlichting.fmw

Parameters:
- SourceDataset_CSV2 = Z:\1. Anwar\AIConsultancy\Datascience Noord NL\DataIn\OVL groningen.csv   # Source CSV (Comma Separated Value) File(s)
- DestDataset_ESRISHAPE = Z:\1. Anwar\AIConsultancy\Datascience Noord NL\DataUit\Openbareverlichting.shp   # Destination Esri Shapefile Folder

Readers:
- CSV2_1: CSV2 from $(SourceDataset_CSV2)

Writers:
- ESRISHAPE_1: ESRISHAPE to $(DestDataset_ESRISHAPE) in EPSG:4326

Note: Auteur: Anwar Ibrahim / Datum: 1-10-2017 / Versie: 0.1 / Omschrijving: / Lat/lon van OVL's omzetten naar een shape.
CSV (reader CSV2_1)
    attributes: longitude string, latitude string, mastnummer string, gemeente string
    -> VertexCreator
VertexCreator
    MODE_NAME = Add Point
    YVAL = @Value(latitude)
    XVAL = @Value(longitude)
    -> CoordinateSystemSetter
CoordinateSystemSetter
    COORDSYS = EPSG:4326
    -> VertexCreator_Output
    -> Openbareverlichting (writer ESRISHAPE_1)
VertexCreator_Output: Inspector
Openbareverlichting (writer ESRISHAPE_1)
    attributes: mastnummer char(254), gemeente char(254), longitude char(254), latitude char(254)
