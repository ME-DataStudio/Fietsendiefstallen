FME workspace 2. BAG.fmw

Parameters:
- SourceDataset_ESRISHAPE = Z:\1. Anwar\AIConsultancy\Datascience Noord NL\DataUit\fietsendiefstal.shp\boundary_500m.shp   # Source Esri Shapefile(s)
- DestDataset_ESRISHAPE = $(FME_MF_DIR)BAG-LL-WGS84.shp   # Destination Esri Shapefile Folder

Readers:
- ESRISHAPE_1: ESRISHAPE from $(SourceDataset_ESRISHAPE) in EPSG:4326

Writers:
- ESRISHAPE_2: ESRISHAPE to $(DestDataset_ESRISHAPE) in EPSG:4326

Note: Auteur: Anwar Ibrahim / Datum: 1-10-2017 / Versie: 0.1 / Omschrijving: / Obv een gebied BAG VBO en PND ophalen van de PDOK WFS en vervolgens wegschrijven naar shape
boundary_500m (reader ESRISHAPE_1)
    attributes: boundar_ID short, AREA number(15,3)
    -> Reprojector
Note: Zet om naar 28992 voor feature reader
Reprojector
    SOURCE = EPSG:4326
    INTERPOLATION_TYPE_NAME = Nearest Neighbor
    DEST = EPSG:28992
    RASTER_CELL_SIZE = Preserve Cells
    REPROJECTED -> FeatureReader [INITIATOR]
Note: FeatureReader [res;ponse paging] / Max Features to Read: 500000 = hoeveel in totaliteit / WFS Count: 1000 = wat geeft de wfs max terug / Aantal loops wordt automatisch bepaald: max/count
FeatureReader
    ATTR_CONFLICT_RES = Use Result
    WFS_COUNT = 1000
    WFS_CLIP_TO_ENVELOPE = NO
    FEATURETYPES = verblijfsobject
    WFS_FLATTEN_XML_FRAGMENTS = NO
    WFS_ENFORCE_PATH_CONTINUITY_BY = SNAPPING_END_POINTS
    COMBINE_GEOM = Use Result
    WFS_DISABLE_XML_NAMESPACE_PROCESSING = NO
    ATTRIBUTES = verblijfsobject,"gml_parent_id,gml_parent_property,gml_id,gid,gid.xsi_nil,identificatie,identificatie.xsi_nil,oppervlakte,oppervlakte.xsi_nil,status,status.xsi_nil,gebruiksdoel,gebruiksdoel.xsi_nil,openbare_ruimte,openbare_ruimte.xsi_nil,huisnummer,huisnummer.xsi_nil,huisletter,huisletter.xsi_nil,toevoeging,toevoeging.xsi_nil,postcode,postcode.xsi_nil,woonplaats,woonplaats.xsi_nil,actualiteitsdatum,actualiteitsdatum.xsi_nil,bouwjaar,bouwjaar.xsi_nil,pandidentificatie,pandidentificatie.xsi_nil,pandstatus,pandstatus.xsi_nil,geometrie,pandgeometrie,fme_geometry{0},fme_geometry{1},fme_geometry{2},fme_geometry{3},fme_geometry{4},fme_geometry{5},fme_geometry{6},fme_geometry{7}"
    WFS_MAX_RESULT_FEATURES = 10000
    WFS_MAP_EMBEDDED_OBJECTS_AS = ATTRIBUTES
    WFS_START_INDEX = 0
    WFS_DISABLE_AUTOMATIC_READER_TYPE_SELECTION = NO
    WFS_PREFERRED_VERSION = 2.0.0
    WFS_CONNECTION_TIMEOUT = 90
    WFS_USE_OLD_READER = NO
    INTERACT = Intersects
    WFS_TRANSFER_TIMEOUT = 90
    WFS_LOCAL_CACHE_EXPIRY = 60
    FORMAT = WFS
    WFS_XML_FRAGMENTS_AS_DOCUMENTS = YES
    WFS_IGNORE_APPLICATON_SCHEMA = no
    ATTR_ACCUM_MODE = Merge Initiator and Result
    WFS_MAP_PREDEFINED_GML_PROPERTIES = NO
    WFS_USE_SEARCH_ENVELOPE = NO
    WFS_MAP_GEOMETRY_COLUMNS = YES
    DATASET = https://geodata.nationaalgeoregister.nl/bag/wfs?request=GetCapabilities
    WFS_MAP_COMPLEX_PROPERTIES_AS = Nested Attributes
    OUTPUT_FEATURES_DISPLAY = Schema and Data Features
    COORDSYS = EPSG:28992
    WFS_PREFER_POST = No
    verblijfsobject -> Deaggregator
Note: haal pnd en vbo uitelkaar
Deaggregator
    ID_SELECTION = ID and Parent ID
    PARENT_ID_ATTR = _hierarchy_parent_id
    EXPLODE_INSTANCES = No
    CHILD_ID_ATTR = _hierarchy_child_id_list
    SPLIT_COMPOSITES = No
    LIST_ATTR_MODE_LOOKUP = LEAN
    GEOM_NAME_FIELD = _geometry_name
    ID_ATTR = _hierarchy_id
    MODE = Flatten One Level
    PART_NUMBER_FIELD = _part_number
    COPY_ATTR = Every Node
    DEAGGREGATED -> AttributeManager
Note: vanwege shape output namen inkorten tot 8
AttributeManager
    ATTR_TABLE:
      REMOVE boundar_ID
      REMOVE AREA
      REMOVE gml_parent_id
      REMOVE gml_parent_property
      REMOVE gml_id
      REMOVE identificatie.xsi_nil
      RENAME_SET_VALUE oppervlakte > opp
      REMOVE oppervlakte.xsi_nil
      REMOVE status.xsi_nil
      RENAME_SET_VALUE gebruiksdoel > gebr_doel
      REMOVE gebruiksdoel.xsi_nil
      REMOVE openbare_ruimte.xsi_nil
      REMOVE huisnummer.xsi_nil
      REMOVE huisletter.xsi_nil
      REMOVE toevoeging.xsi_nil
      REMOVE postcode.xsi_nil
      REMOVE woonplaats.xsi_nil
      REMOVE actualiteitsdatum
      REMOVE actualiteitsdatum.xsi_nil
      REMOVE bouwjaar.xsi_nil
      REMOVE pandidentificatie.xsi_nil
      REMOVE pandstatus.xsi_nil
      REMOVE geometrie
      REMOVE pandgeometrie
      REMOVE fme_geometry{0}
      REMOVE fme_geometry{1}
      REMOVE fme_geometry{2}
      REMOVE fme_geometry{3}
      REMOVE fme_geometry{4}
      REMOVE fme_geometry{5}
      REMOVE fme_geometry{6}
      REMOVE fme_geometry{7}
      REMOVE _hierarchy_child_id_list{}
      REMOVE _geometry_name
      REMOVE _hierarchy_id
      REMOVE _hierarchy_parent_id
      REMOVE _part_number
      REMOVE fme_geometry{}
    -> GeometryFilter
GeometryFilter
    GEOM_PORT_NAMES = Point Area
    BREAK_AGG = No
    POINT -> Reprojector_2
    AREA -> Reprojector_3
Note: naar wgs84
Reprojector_2
    SOURCE = EPSG:28992
    INTERPOLATION_TYPE_NAME = Nearest Neighbor
    DEST = EPSG:4326
    RASTER_CELL_SIZE = Preserve Cells
    REPROJECTED -> CoordinateExtractor
CoordinateExtractor
    IND = 0
    Y_ATTR = lat
    MODE = Specify Coordinate
    X_ATTR = lon
    -> Verblijfsobject (writer ESRISHAPE_2)
Verblijfsobject (writer ESRISHAPE_2)
    attributes: identifica char(200), opp char(200), status char(200), gebr_doel char(200), openbare_r char(200), huisnummer char(200), huisletter char(200), toevoeging char(200), postcode char(200), woonplaats char(200), bouwjaar char(200), pandidenti char(200), pandstatus char(200), gid char(200), gid_xsi_ni char(200), lon char(200), lat char(200)
Reprojector_3
    SOURCE = EPSG:28992
    INTERPOLATION_TYPE_NAME = Nearest Neighbor
    DEST = EPSG:4326
    RASTER_CELL_SIZE = Preserve Cells
    REPROJECTED -> Pand (writer ESRISHAPE_2)
Pand (writer ESRISHAPE_2)
    attributes: identifica char(200), opp char(200), status char(200), gebr_doel char(200), openbare_r char(200), huisnummer char(200), huisletter char(200), toevoeging char(200), postcode char(200), woonplaats char(200), bouwjaar char(200), pandidenti char(200), pandstatus char(200), gid char(200), gid_xsi_ni char(200)
