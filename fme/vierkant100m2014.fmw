FME workspace vierkant100m2014.fmw

Parameters:
- DestDataset_ESRISHAPE = ..\data\vierkant100m2014.zip   # Destination Esri Shapefile Folder
- SourceDataset_WFS = https://geodata.nationaalgeoregister.nl/bestuurlijkegrenzen/wfs?   # Source WFS (Web Feature Service) URL

Readers:
- WFS_1: WFS from $(SourceDataset_WFS)

Writers:
- ESRISHAPE_1: ESRISHAPE to $(DestDataset_ESRISHAPE)

Note: Gemeentegrens Groningen ophalen / Bron: https://www.pdok.nl/nl/service/wfs-bestuurlijke-grenzen
gemeenten (reader WFS_1)
    attributes: gml_parent_id xml_buffer, gml_parent_property xml_buffer, gml_id xml_buffer, code xml_buffer, code.xsi_nil xml_boolean, gemeentenaam xml_buffer, gemeentenaam.xsi_nil xml_boolean, geom xml_geometry
    -> FeatureReader [INITIATOR]
Note: 100 m vierkantstatistieken van het CBS binnen de gemeente Groningen ophalen / Bron: http://nationaalgeoregister.nl/geonetwork/srv/dut/catalog.search#/metadata/1462bbce-ccd3-4362-83d8-4535ca8f44eb
FeatureReader
    DATASET = http://download.cbs.nl/regionale-kaarten/2014-cbs-vierkant-100m.zip
    ESRISHAPE_REPORT_BAD_GEOMETRY = no
    ESRISHAPE_UPPER_CASE_ATTR_NAMES = No
    OUTPUT_FEATURES_DISPLAY = Schema and Data Features
    ESRISHAPE_DISSOLVE_HOLES = no
    ATTRIBUTES = CBSvierkant100m201410,"OBJECTID,C28992R100,INW2000,INW2001,INW2002,INW2003,INW2004,INW2005,INW2006,INW2007,INW2008,INW2009,INW2010,INW2011,INW2012,INW2013,INW2014,TINW_00_10,I2011_014,I2012_014,I2013_014,I2014_014,I2011_1524,I2012_1524,I2013_1524,I2014_1524,I2011_2544,I2012_2544,I2013_2544,I2014_2544,I2011_4564,I2012_4564,I2013_4564,I2014_4564,I2011_65PL,I2012_65PL,I2013_65PL,I2014_65PL,MAN_2011,MAN_2012,MAN_2013,MAN_2014,VROUW_2011,VROUW_2012,VROUW_2013,VROUW_2014,P_AUTO2011,P_AUTO2012,P_AUTO2013,P_AUTO2014,P_WAL2011,P_WAL2012,P_WAL2013,P_WAL2014,P_NWAL2011,P_NWAL2012,P_NWAL2013,P_NWAL2014,WON2000,WON2001,WON2002,WON2003,WON2004,WON2005,WON2006,WON2007,WON2008,WON2009,WON2010,WON2011,WON2012,WOZWON2011,WOZWON2012"
    COMBINE_GEOM = Use Result
    ATTR_ACCUM_MODE = Only Use Result
    ESRISHAPE_SIMPLE_DONUT_GEOMETRY = simple
    ESRISHAPE_CHECK_NUMERIC_FIELDS = yes
    INTERACT = Intersects
    FORMAT = ESRISHAPE
    ESRISHAPE_MEASURES_AS_Z = no
    ESRISHAPE_USE_SEARCH_ENVELOPE = NO
    ESRISHAPE_TRIM_PRECEDING_SPACES = yes
    FEATURETYPES = CBSvierkant100m201410
    CBSvierkant100m201410 -> vierkant100m2014 (writer ESRISHAPE_1)
Note: Wegschrijven als shape-bestand / (EPSG:28992 - RD New)
vierkant100m2014 (writer ESRISHAPE_1)
    attributes: OBJECTID char(200), C28992R100 char(200), INW2000 char(200), INW2001 char(200), INW2002 char(200), INW2003 char(200), INW2004 char(200), INW2005 char(200), INW2006 char(200), INW2007 char(200), INW2008 char(200), INW2009 char(200), INW2010 char(200), INW2011 char(200), INW2012 char(200), INW2013 char(200), INW2014 char(200), TINW_00_10 char(200), I2011_014 char(200), I2012_014 char(200), I2013_014 char(200), I2014_014 char(200), I2011_1524 char(200), I2012_1524 char(200), I2013_1524 char(200), I2014_1524 char(200), I2011_2544 char(200), I2012_2544 char(200), I2013_2544 char(200), I2014_2544 char(200),
      I2011_4564 char(200), I2012_4564 char(200), I2013_4564 char(200), I2014_4564 char(200), I2011_65PL char(200), I2012_65PL char(200), I2013_65PL char(200), I2014_65PL char(200), MAN_2011 char(200), MAN_2012 char(200), MAN_2013 char(200), MAN_2014 char(200), VROUW_2011 char(200), VROUW_2012 char(200), VROUW_2013 char(200), VROUW_2014 char(200), P_AUTO2011 char(200), P_AUTO2012 char(200), P_AUTO2013 char(200), P_AUTO2014 char(200), P_WAL2011 char(200), P_WAL2012 char(200), P_WAL2013 char(200), P_WAL2014 char(200), P_NWAL2011 char(200), P_NWAL2012 char(200), P_NWAL2013 char(200), P_NWAL2014 char(200), WON2000 char(200), WON2001 char(200),
      WON2002 char(200), WON2003 char(200), WON2004 char(200), WON2005 char(200), WON2006 char(200), WON2007 char(200), WON2008 char(200), WON2009 char(200), WON2010 char(200), WON2011 char(200), WON2012 char(200), WOZWON2011 char(200), WOZWON2012 char(200)
