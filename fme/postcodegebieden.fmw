FME workspace postcodegebieden.fmw

Parameters:
- DestDataset_ESRISHAPE_PC6 = ..\data\postcode6.zip   # Destination Esri Shapefile Folder PC6
- DestDataset_ESRISHAPE_PC4 = ..\data\postcode4.zip   # Destination Esri Shapefile Folder PC4
- SourceDataset_WFS = https://geodata.nationaalgeoregister.nl/bestuurlijkegrenzen/wfs?   # Source WFS (Web Feature Service) URL

Readers:
- WFS_1: WFS from $(SourceDataset_WFS)

Writers:
- ESRISHAPE_1: ESRISHAPE to $(DestDataset_ESRISHAPE_PC6)
- ESRISHAPE_2: ESRISHAPE to $(DestDataset_ESRISHAPE_PC4)

Note: Gemeentegrens Groningen ophalen / Bron: https://www.pdok.nl/nl/service/wfs-bestuurlijke-grenzen
gemeenten (reader WFS_1)
    attributes: gml_parent_id xml_buffer, gml_parent_property xml_buffer, gml_id xml_buffer, code xml_buffer, code.xsi_nil xml_boolean, gemeentenaam xml_buffer, gemeentenaam.xsi_nil xml_boolean, geom xml_geometry
    -> FeatureReader [INITIATOR]
Note: Postcodegebieden binnen de gemeente Groningen ophalen / Bron: https://geo.rug.nl/arcgis/rest/services/Administratief/PostcodegebiedenNL/FeatureServer
FeatureReader
    DATASET = https://geo.rug.nl/arcgis/rest/services/Administratief/PostcodegebiedenNL/FeatureServer
    ARCGISFEATURES_QUERY_FEATURE_TYPES_FOR_MERGE_FILTERS = Yes
    OUTPUT_FEATURES_DISPLAY = Schema and Data Features
    ATTRIBUTES = "Postcode 6 polygon","fme_geometry{0},OBJECTID,POSTCODE","Postcode4 polygon","fme_geometry{0},OBJECTID,PC4"
    COMBINE_GEOM = Use Result
    ATTR_ACCUM_MODE = Only Use Result
    INTERACT = Intersects
    FORMAT = ARCGISFEATURES
    ARCGISFEATURES_AUTH_TYPE = None
    ARCGISFEATURES_USE_SEARCH_ENVELOPE = NO
    ARCGISFEATURES_FEATURES_PER_REQUEST = 100000
    FEATURETYPES = "Postcode 6 polygon" "Postcode4 polygon"
    Postcode 6 polygon -> postcode6 (writer ESRISHAPE_1)
    Postcode4 polygon -> postcode4 (writer ESRISHAPE_2)
Note: Output wegschrijven als shape-bestanden (EPSG:28992 - RD New)
postcode6 (writer ESRISHAPE_1)
    attributes: OBJECTID char(200), POSTCODE char(200)
postcode4 (writer ESRISHAPE_2)
    attributes: OBJECTID char(200), PC4 char(200)
