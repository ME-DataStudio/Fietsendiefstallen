FME workspace wijkenbuurtkaart2017.fmw

Parameters:
- SourceDataset_ESRISHAPE = https://www.cbs.nl/-/media/_pdf/2017/36/buurt_2017.zip   # Source Esri Shapefile(s)
- DestDataset_ESRISHAPE_buurt = ..\data\buurt2017.zip   # Destination Esri Shapefile Folder buurten
- DestDataset_ESRISHAPE = ..\data\wijk2017.zip   # Destination Esri Shapefile Folder wijken

Readers:
- ESRISHAPE_2: ESRISHAPE from $(SourceDataset_ESRISHAPE)

Writers:
- ESRISHAPE_1: ESRISHAPE to $(DestDataset_ESRISHAPE_buurt)
- ESRISHAPE_3: ESRISHAPE to $(DestDataset_ESRISHAPE)

buurt_2017 (reader ESRISHAPE_2)
    attributes: BU_CODE char(10), BU_NAAM char(60), WK_CODE char(8), GM_CODE char(6), GM_NAAM char(60), IND_WBI long, WATER char(4), POSTCODE char(10), DEK_PERC long, OAD long, STED long, AANT_INW long, AANT_MAN long, AANT_VROUW long, P_00_14_JR long, P_15_24_JR long, P_25_44_JR long, P_45_64_JR long, P_65_EO_JR long, P_ONGEHUWD long, P_GEHUWD long, P_GESCHEID long, P_VERWEDUW long, BEV_DICHTH long, AANTAL_HH long, P_EENP_HH long, P_HH_Z_K long, P_HH_M_K long, GEM_HH_GR float, P_WEST_AL long,
      P_N_W_AL long, P_MAROKKO long, P_ANT_ARU long, P_SURINAM long, P_TURKIJE long, P_OVER_NW long, OPP_TOT long, OPP_LAND long, OPP_WATER long
    -> TestFilter
TestFilter
    TEST_LIST = BOOL_OP,OR,COMPOSITE_TEST,<Unused>,TEST_CLAUSE,"TEST @Value(GM_NAAM) = Groningen",Gemeente Groningen
    DEFAULT_VALUE = <UNFILTERED>
    Gemeente Groningen -> buurt2017 (writer ESRISHAPE_1)
buurt2017 (writer ESRISHAPE_1)
    attributes: BU_CODE char(10), BU_NAAM char(60), WK_CODE char(8), GM_CODE char(6), GM_NAAM char(60), IND_WBI long, WATER char(4), POSTCODE char(10), DEK_PERC long, OAD long, STED long, AANT_INW long, AANT_MAN long, AANT_VROUW long, P_00_14_JR long, P_15_24_JR long, P_25_44_JR long, P_45_64_JR long, P_65_EO_JR long, P_ONGEHUWD long, P_GEHUWD long, P_GESCHEID long, P_VERWEDUW long, BEV_DICHTH long, AANTAL_HH long, P_EENP_HH long, P_HH_Z_K long, P_HH_M_K long, GEM_HH_GR float, P_WEST_AL long,
      P_N_W_AL long, P_MAROKKO long, P_ANT_ARU long, P_SURINAM long, P_TURKIJE long, P_OVER_NW long, OPP_TOT long, OPP_LAND long, OPP_WATER long
wijk_2017 (reader ESRISHAPE_2)
    attributes: WK_CODE char(8), WK_NAAM char(60), GM_CODE char(6), GM_NAAM char(60), IND_WBI long, WATER char(4), OAD long, STED long, AANT_INW long, AANT_MAN long, AANT_VROUW long, P_00_14_JR long, P_15_24_JR long, P_25_44_JR long, P_45_64_JR long, P_65_EO_JR long, P_ONGEHUWD long, P_GEHUWD long, P_GESCHEID long, P_VERWEDUW long, BEV_DICHTH long, AANTAL_HH long, P_EENP_HH long, P_HH_Z_K long, P_HH_M_K long, GEM_HH_GR float, P_WEST_AL long, P_N_W_AL long, P_MAROKKO long, P_ANT_ARU long,
      P_SURINAM long, P_TURKIJE long, P_OVER_NW long, OPP_TOT long, OPP_LAND long, OPP_WATER long
    -> TestFilter_2
TestFilter_2
    TEST_LIST = BOOL_OP,OR,COMPOSITE_TEST,<Unused>,TEST_CLAUSE,"TEST @Value(GM_NAAM) = Groningen",Gemeente Groningen
    DEFAULT_VALUE = <UNFILTERED>
    Gemeente Groningen -> wijk2017 (writer ESRISHAPE_3)
wijk2017 (writer ESRISHAPE_3)
    attributes: WK_CODE char(8), WK_NAAM char(60), GM_CODE char(6), GM_NAAM char(60), IND_WBI long, WATER char(4), OAD long, STED long, AANT_INW long, AANT_MAN long, AANT_VROUW long, P_00_14_JR long, P_15_24_JR long, P_25_44_JR long, P_45_64_JR long, P_65_EO_JR long, P_ONGEHUWD long, P_GEHUWD long, P_GESCHEID long, P_VERWEDUW long, BEV_DICHTH long, AANTAL_HH long, P_EENP_HH long, P_HH_Z_K long, P_HH_M_K long, GEM_HH_GR float, P_WEST_AL long, P_N_W_AL long, P_MAROKKO long, P_ANT_ARU long,
      P_SURINAM long, P_TURKIJE long, P_OVER_NW long, OPP_TOT long, OPP_LAND long, OPP_WATER long
